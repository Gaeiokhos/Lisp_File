(defun c:fr ()

(setq fr1 (getfiled "Select Block" "N:/HullProjects/dxfout/p179/900/sheet/900-midship-1" "dxf" 0))
(command "insert" fr1 "0,0,0" "1" "1" "0")
(command "Enter")
(setq fr2 (getfiled "Select Block" "N:/HullProjects/dxfout/p179/900/sheet/900-midship-11" "dxf" 0))
(command "insert" fr2 "61450,0,0" "1" "1" "0")
(command "Enter")
(setq fr3 (getfiled "Select Block" "N:/HullProjects/dxfout/p179/900/sheet/900-midship-2" "dxf" 0))
(command "insert" fr3 "122900,0,0" "1" "1" "0")
(command "Enter")
(setq fr4 (getfiled "Select Block" "N:/HullProjects/dxfout/p179/900/sheet/900-midship-22" "dxf" 0))
(command "insert" fr4 "184350,0,0" "1" "1" "0")
(command "Enter")
(setq fr5 (getfiled "Select Block" "N:/HullProjects/dxfout/p179/900/sheet/900-midship-3" "dxf" 0))
(command "insert" fr5 "245800,0,0" "1" "1" "0")
(command "Enter")
(setq fr55 (getfiled "Select Block" "N:/HullProjects/dxfout/p179/900/sheet/900-midship-33" "dxf" 0))
(command "insert" fr55 "0,-44050,0" "1" "1" "0")
(command "Enter")
(setq fr6 (getfiled "Select Block" "N:/HullProjects/dxfout/p179/900/sheet/900-midship-4" "dxf" 0))
(command "insert" fr6 "61450,-44050,0" "1" "1" "0")
(command "Enter")
(setq fr7 (getfiled "Select Block" "N:/HullProjects/dxfout/p179/900/sheet/900-midship-44" "dxf" 0))
(command "insert" fr7 "122900,-44050,0" "1" "1" "0")
(command "Enter")
(setq fr8 (getfiled "Select Block" "N:/HullProjects/dxfout/p179/900/sheet/900-midship-5" "dxf" 0))
(command "insert" fr8 "184350,-44050,0" "1" "1" "0")
(command "Enter")
(setq fr9 (getfiled "Select Block" "N:/HullProjects/dxfout/p179/900/sheet/900-midship-55" "dxf" 0))
(command "insert" fr9 "245800,-44050,0" "1" "1" "0")
(command "Enter")
(setq fr10 (getfiled "Select Block" "N:/HullProjects/dxfout/p179/900/sheet/900-midship-6" "dxf" 0))
(command "insert" fr10 "0,-88100,0" "1" "1" "0")
(command "Enter")
(setq fr11 (getfiled "Select Block" "N:/HullProjects/dxfout/p179/900/sheet/900-midship-7" "dxf" 0))
(command "insert" fr11 "61450,-88100,0" "1" "1" "0")
(command "Enter")
(setq fr12 (getfiled "Select Block" "N:/HullProjects/dxfout/p179/900/sheet/900-midship-77" "dxf" 0))
(command "insert" fr12 "122900,-88100,0" "1" "1" "0")
(command "Enter")
(setq fr13 (getfiled "Select Block" "N:/HullProjects/dxfout/p179/900/sheet/900-midship-8" "dxf" 0))
(command "insert" fr13 "184350,-88100,0" "1" "1" "0")
(command "Enter")
(setq fr14 (getfiled "Select Block" "N:/HullProjects/dxfout/p179/900/sheet/900-midship-9" "dxf" 0))
(command "insert" fr14 "245800,-88100,0" "1" "1" "0")
(command "Enter")
(setq fr15 (getfiled "Select Block" "N:/HullProjects/dxfout/p179/900/sheet/900-midship-10" "dxf" 0))
(command "insert" fr15 "0,-132150,0" "1" "1" "0")
(command "Enter")
)
